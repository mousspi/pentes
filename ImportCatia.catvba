Attribute VB_Name = "Module1"
Sub ImportPointsFromCSV()
    Dim filePath As String
    filePath = "C:\Users\HPProbook\Documents\Dev\pentes\13216_virgules.csv" ' Remplacez par le chemin de votre fichier CSV

    Dim fileNum As Integer
    fileNum = FreeFile

    Open filePath For Input As #fileNum
    
    Dim lineInput_ As String
    Dim coordinates() As String
    Dim x As Double, y As Double, z As Double

    Do While Not EOF(fileNum)
        Line Input #fileNum, lineInput_
        coordinates = Split(lineInput_, ";")

        x = CDbl(coordinates(0))
        y = CDbl(coordinates(1))
        z = CDbl(coordinates(2))

        Dim hybridBody As hybridBody
        Set hybridBody = CATIA.ActiveDocument.Part.HybridBodies.Add
        hybridBody.Name = "PointsFromCSV"

        Dim hybridShapeFactory As hybridShapeFactory
        Set hybridShapeFactory = CATIA.ActiveDocument.Part.hybridShapeFactory

        Dim point As HybridShapePointCoord
        Set point = hybridShapeFactory.AddNewPointCoord(x, y, z)
        hybridBody.AppendHybridShape point

    Loop

    Close #fileNum
End Sub
